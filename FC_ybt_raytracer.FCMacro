# -*- coding: utf-8 -*-
"""
FC_ybt_raytracer.FCMacro -- başlatıcı
FreeCAD içinde yerleşik numpy ışın izleyici. Asıl kod yanındaki `ybt_raytracer/` klasöründedir;
bu dosya ve klasör AYNI yerde (Macro klasörü) durmalıdır.
Kullanım: Macro > Macros... > bu dosyayı çalıştır.
"""
__Name__ = "FC YBT Raytracer"
__Comment__ = "Dependency-free numpy ray tracer: shadows, glass, reflections, HDRI lighting, materials and textures"
__Author__ = "sedatkrn"
__Date__ = "2026-10-31"
__Version__ = "1.6.2"
__License__ = "MIT"
__Web__ = "https://github.com/sedatkrn/FC_YBTRayTracer"
__Icon__ = "FC_ybt_raytracer.png"
__Help__ = "Run the macro, set the options in the panel and press Render"
__Status__ = "Stable"
__Communication__ = "https://github.com/sedatkrn/FC_YBTRayTracer/issues"

import os
import sys
import importlib

def _find_here():
    """Başlatıcının klasörü: ybt_raytracer/ paketi bu klasörde olmalı."""
    cands = []
    try:
        cands.append(os.path.dirname(os.path.abspath(__file__)))
    except NameError:
        pass
    try:
        cands.append(os.path.dirname(os.path.abspath(sys._getframe().f_code.co_filename)))
    except Exception:
        pass
    try:
        import FreeCAD
        cands.append(FreeCAD.getUserMacroDir(True))
        cands.append(FreeCAD.ParamGet("User parameter:BaseApp/Preferences/Macro").GetString("MacroPath", ""))
    except Exception:
        pass
    try:                                # Addon Manager depoyu Mod/ altına da koyabilir
        import FreeCAD
        for base in (FreeCAD.getUserAppDataDir(), FreeCAD.getHomePath()):
            moddir = os.path.join(base, "Mod")
            if os.path.isdir(moddir):
                for sub in sorted(os.listdir(moddir)):
                    cands.append(os.path.join(moddir, sub))
    except Exception:
        pass
    for c in cands:
        if c and os.path.isdir(os.path.join(c, "ybt_raytracer")):
            return c
    raise RuntimeError("ybt_raytracer/ klasörü başlatıcı makroyla aynı yerde bulunamadı. Denenen: %s" % cands)


_HERE = _find_here()
if _HERE not in sys.path:
    sys.path.insert(0, _HERE)

# makro tekrar çalıştırılınca güncel kodu yükle (FreeCAD'i yeniden başlatmadan)
for _m in [m for m in list(sys.modules) if m == "ybt_raytracer" or m.startswith("ybt_raytracer.")]:
    del sys.modules[_m]

try:
    import FreeCADGui  # noqa: F401
    _IN_FREECAD = True
except ImportError:
    _IN_FREECAD = False

if _IN_FREECAD:
    from ybt_raytracer.ui import main
    main()
